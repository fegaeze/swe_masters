# controller

## HLR1: System initialization (Functional)
Upon resumption of power to the controller, no signals shall be displayed for a time not less than x seconds nor greater than y seconds before normal operations begin.

### HLR1.1: Startup delay condition (Functional)
If the system has already been turned off for more than x seconds, the system shall skip the start up delay. Otherwise, the system shall start operations only after a fixed delay.

### HLR1.2: Resumption of normal operations (Functional)
The controller shall resume operation at "Vehicles Passing Ready" phase. That is, a yellow light signal for the vehicle light set and a red light signal for the pedestrian light set.

## HLR2: Default light signals (Functional)
The traffic lights for both carriageways shall remain in one default configuration until a call button on either side of the carriageway is pressed. This configuration is green for the vehicle light set and red for the pedestrian light set.

## HLR3: Call button response (Container)
When the call button on either carriageway is pressed, the system shall initiate the sequence for light transition to green for pedestrians and red for motorists.

### HLR3.1: Pedestrian crossing wait time (Functional)
When the call button on either carriageway is pressed, the system shall signal the pedestrian to cross in no longer than x seconds.

### HLR3.2: Dual carriageway response (Functional)
The system shall automatically trigger a button press on the other carriageway after x seconds when the call button on either carriageway is pressed

### HLR3.3: Button request during light sequence (Functional)
When the call button on either carriageway is pressed and the light sequence has initiated, the system shall not service any new requests.

## HLR5: Traffic lights regime (Functional)
The traffic lights shall be switched based on the standard lights regime: Green - Yellow - Red and vice versa. The yellow lights must always be between the green and red lights transitions.

### HLR5.1: Green signal sonstraint (Functional)
The vehicle and pedestrian light set on one carriageway must never be green at the same time.

### HLR5.2: Single light display on light set at a given time (Functional)
When the light switching occurs, each signal head must display no more than one light signal at a time.

### HLR5.3: Vehicle Passing Efficiency (Functional)
x seconds after the pedestrian light set has been switched to red, vehicle light set shall be switched to green.
